module ietf-6tisch-brski {
  yang-version 1.1;

  namespace
    "urn:ietf:params:xml:ns:yang:6tisch-brski";
  prefix "ietf6brski";

  //import ietf-yang-types { prefix yang; }
  //import ietf-inet-types { prefix inet; }

  organization
   "IETF 6tisch Working Group";

  contact
   "WG Web:   <http://tools.ietf.org/wg/6tisch/>
    WG List:  <mailto:6tisch@ietf.org>
    Author:   Michael Richardson
              <mailto:mcr+ietf@sandelman.ca>";

  description
   "This module defines an interface to set and retrieve
    BRSKI objects using CoMI.  This interface is used
    as part of an enrollment process for constrained
    nodes and networks.";

  revision "2017-03-01" {
    description
     "Initial version";
    reference
     "RFC XXXX: 6tisch zero-touch bootstrap";
  }

  // top-level container
  container ietf6brski {
    leaf requestnonce {
      type binary;
      length XX;    // how big can/should it be?
      mandatory true;
      description "Request Nonce.";
    }
    leaf voucher {
      type binary;
      description "The voucher as a serialized COSE object";
    }

    leaf csrattributes {
      type binary;
      description "A list of attributes that MUST be in the CSR";
    }

    leaf certificaterequest {
      type binary;
      description "A PKIX format Certificate Request";
    }

    leaf certificate {
      type binary;
      description "The LDevID certificate";
    }
  }
}
